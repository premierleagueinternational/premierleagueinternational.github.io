FME workspace arcLayerCreation.fmw

Parameters:
- SourceDataset_CSV2 = $(FME_MF_DIR)players_20.csv   # Source CSV (Comma Separated Value) File(s)
- SourceDataset_CSV2_5 = $(FME_MF_DIR)country_centroids_az8.csv   # Source CSV (Comma Separated Value) File(s)
- SourceDataset_GEOJSON = $(FME_MF_DIR)TeamLocations.geojson   # Source GeoJSON File or URL
- DestDataset_JSON = $(FME_MF_DIR)TeamsArcs\Bournemouth.json   # Destination JSON (JavaScript Object Notation) File
- DestDataset_JSON_33 = $(FME_MF_DIR)TeamsArcs\Arsenal.json   # Destination JSON (JavaScript Object Notation) File
- DestDataset_JSON_25 = $(FME_MF_DIR)TeamsArcs\AstonVilla.json   # Destination JSON (JavaScript Object Notation) File
- DestDataset_JSON_41 = $(FME_MF_DIR)TeamsArcs\Brighton.json   # Destination JSON (JavaScript Object Notation) File
- DestDataset_JSON_29 = $(FME_MF_DIR)TeamsArcs\Burnley.json   # Destination JSON (JavaScript Object Notation) File
- DestDataset_JSON_37 = $(FME_MF_DIR)TeamsArcs\Chelsea.json   # Destination JSON (JavaScript Object Notation) File
- DestDataset_JSON_23 = $(FME_MF_DIR)TeamsArcs\CrystalPalace.json   # Destination JSON (JavaScript Object Notation) File
- DestDataset_JSON_27 = $(FME_MF_DIR)TeamsArcs\Everton.json   # Destination JSON (JavaScript Object Notation) File
- DestDataset_JSON_31 = $(FME_MF_DIR)TeamsArcs\Leicester.json   # Destination JSON (JavaScript Object Notation) File
- DestDataset_JSON_35 = $(FME_MF_DIR)TeamsArcs\Liverpool.json   # Destination JSON (JavaScript Object Notation) File
- DestDataset_JSON_22 = $(FME_MF_DIR)TeamsArcs\ManCity.json   # Destination JSON (JavaScript Object Notation) File
- DestDataset_JSON_39 = $(FME_MF_DIR)TeamsArcs\ManUtd.json   # Destination JSON (JavaScript Object Notation) File
- DestDataset_JSON_24 = $(FME_MF_DIR)TeamsArcs\Newcastle.json   # Destination JSON (JavaScript Object Notation) File
- DestDataset_JSON_26 = $(FME_MF_DIR)TeamsArcs\Norwich.json   # Destination JSON (JavaScript Object Notation) File
- DestDataset_JSON_28 = $(FME_MF_DIR)TeamsArcs\SheffieldUtd.json   # Destination JSON (JavaScript Object Notation) File
- DestDataset_JSON_30 = $(FME_MF_DIR)TeamsArcs\Southampton.json   # Destination JSON (JavaScript Object Notation) File
- DestDataset_JSON_32 = $(FME_MF_DIR)TeamsArcs\Tottenham.json   # Destination JSON (JavaScript Object Notation) File
- DestDataset_JSON_34 = $(FME_MF_DIR)TeamsArcs\Watford.json   # Destination JSON (JavaScript Object Notation) File
- DestDataset_JSON_36 = $(FME_MF_DIR)TeamsArcs\WestHam.json   # Destination JSON (JavaScript Object Notation) File
- DestDataset_JSON_38 = $(FME_MF_DIR)TeamsArcs\Wolverhampton.json   # Destination JSON (JavaScript Object Notation) File
- SourceDataset_GEOJSON_3 = $(FME_MF_DIR)TeamLocations.geojson   # Source GeoJSON File or URL
- DestDataset_GEOJSON = $(FME_MF_DIR)Clubs.json   # Destination GeoJSON File
- SourceDataset_CSV2_4 = $(FME_MF_DIR)country_centroids.csv   # Source CSV (Comma Separated Value) File(s)
- DestDataset_JSON_40 = $(FME_MF_DIR)Countries.json   # Destination JSON (JavaScript Object Notation) File

Readers:
- CSV2_1: CSV2 from $(SourceDataset_CSV2)
- CSV2_2: CSV2 from $(SourceDataset_CSV2_5)
- GEOJSON_1: GEOJSON from $(SourceDataset_GEOJSON)
- GEOJSON_2: GEOJSON from $(SourceDataset_GEOJSON_3)
- CSV2_3: CSV2 from $(SourceDataset_CSV2_4)

Writers:
- JSON_1: JSON to $(DestDataset_JSON)
- JSON_2: JSON to $(DestDataset_JSON_33)
- JSON_3: JSON to $(DestDataset_JSON_25)
- JSON_4: JSON to $(DestDataset_JSON_41)
- JSON_5: JSON to $(DestDataset_JSON_29)
- JSON_6: JSON to $(DestDataset_JSON_37)
- JSON_7: JSON to $(DestDataset_JSON_23)
- JSON_8: JSON to $(DestDataset_JSON_27)
- JSON_9: JSON to $(DestDataset_JSON_31)
- JSON_10: JSON to $(DestDataset_JSON_35)
- JSON_11: JSON to $(DestDataset_JSON_22)
- JSON_12: JSON to $(DestDataset_JSON_39)
- JSON_13: JSON to $(DestDataset_JSON_24)
- JSON_14: JSON to $(DestDataset_JSON_26)
- JSON_15: JSON to $(DestDataset_JSON_28)
- JSON_16: JSON to $(DestDataset_JSON_30)
- JSON_17: JSON to $(DestDataset_JSON_32)
- JSON_18: JSON to $(DestDataset_JSON_34)
- JSON_19: JSON to $(DestDataset_JSON_36)
- JSON_20: JSON to $(DestDataset_JSON_38)
- GEOJSON_3: GEOJSON to $(DestDataset_GEOJSON)
- JSON_21: JSON to $(DestDataset_JSON_40)

CSV (reader CSV2_3)
    attributes: FID string, the_geom string, FID_ uint8, scalerank uint8, featurecla string, labelrank uint8, sovereignt string, sov_a3 string, adm0_dif uint8, level uint8, type string, admin string, adm0_a3 string, geou_dif uint8, geounit string, gu_a3 string, su_dif uint8, subunit string, su_a3 string, brk_diff uint8, name string, name_long string, brk_a3 string, brk_name string, brk_group string, abbrev string, postal string, formal_en string, formal_fr string, note_adm0 string,
      note_brk string, name_sort string, name_alt string, mapcolor7 string, mapcolor8 uint8, mapcolor9 uint8, mapcolor13 int8, pop_est int32, gdp_md_est real64, pop_year real64, lastcensus int16, gdp_year int16, economy string, income_grp string, wikipedia string, fips_10 int8, iso_a2 string, iso_a3 string, iso_n3 string, un_a3 int16, wb_a2 string, wb_a3 string, woe_id string, adm0_a3_is string, adm0_a3_us string, adm0_a3_un string, adm0_a3_wb int8, continent string, region_un string, subregion string,
      region_wb string, name_len string, long_len real64, abbrev_len uint8, tiny int8, homepart int8, Longitude x_coordinate, Latitude y_coordinate, col68 real64
    -> FeatureMerger_2 [SUPPLIER]
FeatureMerger_2
    ATTR_ACCUM_MODE = Prefix Supplier
    IGNORE_NULLS = No
    JOIN_KEYS = @Value(nationality) @Value(name_long) AUTO
    MERGE_TYPE = Attributes Only
    PROCESS_DUPS = NO
    REJECT_NULL_MISSING_KEYS = No
    SUPPLIERS_FIRST = No
    SUPPLIER_PREFIX = _sup
    MERGED -> AttributeRemover_2
AttributeRemover_2
    REMOVE_ATTRS = _supabbrev,_supabbrev_len,_supadm0_a3,_supadm0_a3_is,_supadm0_a3_un,_supadm0_a3_us,_supadm0_a3_wb,_supadm0_dif,_supadmin,_supbrk_a3,_supbrk_diff,_supbrk_group,_supbrk_name,_supcontinent,_supeconomy,_supfeaturecla,_supFID,_supFID_,_supfips_10,_supformal_en,_supformal_fr,_supgdp_md_est,_supgdp_year,_supgeou_dif,_supgeounit,_supgu_a3,_suphomepart,_supincome_grp,_supiso_a2,_supiso_a3,_supiso_n3,_suplabelrank,_suplastcensus,_suplevel,_suplong_len,_supmapcolor7,_supmapcolor8,_supmapcolor9,_supmapcolor13,_supname,_supname_alt,_supname_len,_supname_sort,_supnote_adm0,_supnote_brk,_suppop_est,_suppop_year,_suppostal,_supregion_un,_supregion_wb,_supscalerank,_supsov_a3,_supsovereignt,_supsu_a3,_supsu_dif,_supsubregion,_supsubunit,_supthe_geom,_suptiny,_suptype,_supun_a3,_supwb_a2,_supwb_a3,_supwikipedia,_supwoe_id
    -> FeatureMerger [SUPPLIER]
FeatureMerger
    ATTR_ACCUM_MODE = Prefix Supplier
    IGNORE_NULLS = No
    JOIN_KEYS = @Value(Team) @Value(club) AUTO
    LIST_ATTRS_TO_INCLUDE = age club long_name nationality player_url short_name _supLatitude _supLongitude
    LIST_NAME = playerRelation
    MERGE_TYPE = Attributes Only
    PROCESS_DUPS = NO
    REJECT_NULL_MISSING_KEYS = No
    SUPPLIERS_FIRST = No
    SUPPLIER_PREFIX = _sup
    MERGED -> AttributeRemover
AttributeRemover
    REMOVE_ATTRS = _supage,_supattacking_crossing,_supattacking_finishing,_supattacking_heading_accuracy,_supattacking_short_passing,_supattacking_volleys,_supbody_type,_supcam,_supcb,_supcdm,_supcf,_supclub,_supcm,_supcontract_valid_until,_supdefending,_supdefending_marking,_supdefending_sliding_tackle,_supdefending_standing_tackle,_supdob,_supdribbling,_supgk_diving,_supgk_handling,_supgk_kicking,_supgk_positioning,_supgk_reflexes,_supgk_speed,_supgoalkeeping_diving,_supgoalkeeping_handling,_supgoalkeeping_kicking,_supgoalkeeping_positioning,_supgoalkeeping_reflexes,_supheight_cm,_supinternational_reputation,_supjoined,_suplam,_suplb,_suplcb,_suplcm,_supldm,_suplf,_suplm,_suploaned_from,_suplong_name,_supls,_suplw,_suplwb,_supmentality_aggression,_supmentality_composure,_supmentality_interceptions,_supmentality_penalties,_supmentality_positioning,_supmentality_vision,_supmovement_acceleration,_supmovement_agility,_supmovement_balance,_supmovement_reactions,_supmovement_sprint_speed,_supnation_jersey_number,_supnation_position,_supnationality,_supoverall,_suppace,_suppassing,_supphysic,_supplayer_positions,_supplayer_tags,_supplayer_traits,_supplayer_url,_suppotential,_suppower_jumping,_suppower_long_shots,_suppower_shot_power,_suppower_stamina,_suppower_strength,_suppreferred_foot,_supram,_suprb,_suprcb,_suprcm,_suprdm,_supreal_face,_suprelease_clause_eur,_suprf,_suprm,_suprs,_suprw,_suprwb,_supshooting,_supshort_name,_supskill_ball_control,_supskill_curve,_supskill_dribbling,_supskill_fk_accuracy,_supskill_long_passing,_supskill_moves,_supsofifa_id,_supst,_supteam_jersey_number,_supteam_position,_supvalue_eur,_supwage_eur,_supweak_foot,_supweight_kg,_supwork_rate,_sup_supLatitude,_sup_supLongitude,_sup_supname_long
    -> ListExploder
ListExploder
    ATTR_ACCUM_MODE = Merge List Attributes
    ATTR_CONFLICT_RES = Use List Attribute Values
    INDEX_ATTR = _element_index
    LIST_ATTR = playerRelation{}
    ELEMENTS -> StringConcatenator
StringConcatenator
    ACTION = Create New Attribute
    PARM_LINE = fme_basicstring:17%1%1%1:@Value(long_name)
    VAL_ATTR = nameANDurl
    -> AttributeManager
AttributeManager
    ATTR_TABLE:
      REMOVE HomeTeam
      SET_TO
      REMOVE FDCOUK
      REMOVE City
      REMOVE Stadium
      REMOVE Capacity
      REMOVE Latitude
      REMOVE Longitude
      REMOVE Country
      RENAME_SET_VALUE _supLongitude > LongCentroid
      RENAME_SET_VALUE _supLatitude > LatCentroid
      REMOVE _element_index
    -> UniqueValueLogger
    -> PointOnPointOverlayer [POINT]
    -> GeometryRemover
Note: NOW CALCULATE SOME INDICATOR OF INTERNATIONALITY
Aggregator_22
    ACCUM_ATTRS_NAME = Use Attributes From One Feature
    AGGREGATE_TYPE = Homogeneous Collection (If Possible)
    GROUP_BY = value
    MODE = Geometry - Assemble One Level
    SEP = ,
    AGGREGATE -> Aggregator_22_Aggregate
Aggregator_22_Aggregate: Inspector
GeometryRemover
    -> VertexCreator
VertexCreator
    MEASURE_TYPE = Continuous
    MISSING_VAL_MODE = Compute
    MODE_NAME = Add Point
    XVAL = @Value(LongCentroid)
    YVAL = @Value(LatCentroid)
    -> AttributeRemover_4 [off]
    -> AttributeFilter
AttributeRemover_4 [off]
    REMOVE_ATTRS = LatCentroid,LongCentroid
    -> AttributeFilter [off]
AttributeFilter
    ATTR_NAME = Team
    ATTR_VALUES = <Empty>,<Missing>,<Null>,<Unfiltered>,Arsenal ,Aston Villa ,Brighton & Hove Albion ,Burnley ,Chelsea ,Crystal Palace ,Everton ,Leicester City ,Liverpool ,Manchester City ,Manchester United ,Newcastle United ,Norwich City ,Sheffield United,Southampton ,Tottenham Hotspur ,Watford ,West Ham United ,Wolverhampton Wanderers ,Bournemouth
    Arsenal -> Aggregator_11
    Aston Villa -> Aggregator_10
    Brighton & Hove Albion -> Aggregator_8
    Burnley -> Aggregator_7
    Chelsea -> Aggregator_21
    Crystal Palace -> Aggregator_20
    Everton -> Aggregator_19
    Leicester City -> Aggregator_18
    Liverpool -> Aggregator_17
    Manchester City -> Aggregator_16
    Manchester United -> Aggregator_15
    Newcastle United -> Aggregator_14
    Norwich City -> Aggregator_13
    Sheffield United -> Aggregator_12
    Southampton -> Aggregator_6
    Tottenham Hotspur -> Aggregator_5
    Watford -> Aggregator_4
    West Ham United -> Aggregator_3
    Wolverhampton Wanderers -> Aggregator_2
    Bournemouth -> Aggregator
    Bournemouth -> Aggregator_9
Aggregator_21
    ACCUM_ATTRS_NAME = Use Attributes From One Feature
    AGGREGATE_TYPE = Homogeneous Collection (If Possible)
    GROUP_BY = nationality
    LIST_ATTRS_TO_INCLUDE = nameANDurl
    LIST_NAME = names
    MODE = Geometry - Assemble One Level
    SEP = ,
    AGGREGATE -> ListConcatenator_21
ListConcatenator_21
    DROP_EMPTY_PARTS = No
    LIST_ATTR = names{}.nameANDurl
    SEP = ;
    VAL_ATTR = PlayerLink
    -> FeatureMerger_6 [REQUESTOR]
Aggregator_20
    ACCUM_ATTRS_NAME = Use Attributes From One Feature
    AGGREGATE_TYPE = Homogeneous Collection (If Possible)
    GROUP_BY = nationality
    LIST_ATTRS_TO_INCLUDE = nameANDurl
    LIST_NAME = names
    MODE = Geometry - Assemble One Level
    SEP = ,
    AGGREGATE -> ListConcatenator_20
ListConcatenator_20
    DROP_EMPTY_PARTS = No
    LIST_ATTR = names{}.nameANDurl
    SEP = ;
    VAL_ATTR = PlayerLink
    -> FeatureMerger_6 [REQUESTOR]
Aggregator_19
    ACCUM_ATTRS_NAME = Use Attributes From One Feature
    AGGREGATE_TYPE = Homogeneous Collection (If Possible)
    GROUP_BY = nationality
    LIST_ATTRS_TO_INCLUDE = nameANDurl
    LIST_NAME = names
    MODE = Geometry - Assemble One Level
    SEP = ,
    AGGREGATE -> ListConcatenator_19
ListConcatenator_19
    DROP_EMPTY_PARTS = No
    LIST_ATTR = names{}.nameANDurl
    SEP = ;
    VAL_ATTR = PlayerLink
    -> FeatureMerger_6 [REQUESTOR]
Aggregator_18
    ACCUM_ATTRS_NAME = Use Attributes From One Feature
    AGGREGATE_TYPE = Homogeneous Collection (If Possible)
    GROUP_BY = nationality
    LIST_ATTRS_TO_INCLUDE = nameANDurl
    LIST_NAME = names
    MODE = Geometry - Assemble One Level
    SEP = ,
    AGGREGATE -> ListConcatenator_18
ListConcatenator_18
    DROP_EMPTY_PARTS = No
    LIST_ATTR = names{}.nameANDurl
    SEP = ;
    VAL_ATTR = PlayerLink
    -> FeatureMerger_6 [REQUESTOR]
Aggregator_17
    ACCUM_ATTRS_NAME = Use Attributes From One Feature
    AGGREGATE_TYPE = Homogeneous Collection (If Possible)
    GROUP_BY = nationality
    LIST_ATTRS_TO_INCLUDE = nameANDurl
    LIST_NAME = names
    MODE = Geometry - Assemble One Level
    SEP = ,
    AGGREGATE -> ListConcatenator_17
ListConcatenator_17
    DROP_EMPTY_PARTS = No
    LIST_ATTR = names{}.nameANDurl
    SEP = ;
    VAL_ATTR = PlayerLink
    -> FeatureMerger_6 [REQUESTOR]
Aggregator_16
    ACCUM_ATTRS_NAME = Use Attributes From One Feature
    AGGREGATE_TYPE = Homogeneous Collection (If Possible)
    GROUP_BY = nationality
    LIST_ATTRS_TO_INCLUDE = nameANDurl
    LIST_NAME = names
    MODE = Geometry - Assemble One Level
    SEP = ,
    AGGREGATE -> ListConcatenator_16
ListConcatenator_16
    DROP_EMPTY_PARTS = No
    LIST_ATTR = names{}.nameANDurl
    SEP = ;
    VAL_ATTR = PlayerLink
    -> FeatureMerger_6 [REQUESTOR]
Aggregator_15
    ACCUM_ATTRS_NAME = Use Attributes From One Feature
    AGGREGATE_TYPE = Homogeneous Collection (If Possible)
    GROUP_BY = nationality
    LIST_ATTRS_TO_INCLUDE = nameANDurl
    LIST_NAME = names
    MODE = Geometry - Assemble One Level
    SEP = ,
    AGGREGATE -> ListConcatenator_15
ListConcatenator_15
    DROP_EMPTY_PARTS = No
    LIST_ATTR = names{}.nameANDurl
    SEP = ;
    VAL_ATTR = PlayerLink
    -> FeatureMerger_6 [REQUESTOR]
Aggregator_14
    ACCUM_ATTRS_NAME = Use Attributes From One Feature
    AGGREGATE_TYPE = Homogeneous Collection (If Possible)
    GROUP_BY = nationality
    LIST_ATTRS_TO_INCLUDE = nameANDurl
    LIST_NAME = names
    MODE = Geometry - Assemble One Level
    SEP = ,
    AGGREGATE -> ListConcatenator_14
ListConcatenator_14
    DROP_EMPTY_PARTS = No
    LIST_ATTR = names{}.nameANDurl
    SEP = ;
    VAL_ATTR = PlayerLink
    -> FeatureMerger_6 [REQUESTOR]
Aggregator_13
    ACCUM_ATTRS_NAME = Use Attributes From One Feature
    AGGREGATE_TYPE = Homogeneous Collection (If Possible)
    GROUP_BY = nationality
    LIST_ATTRS_TO_INCLUDE = nameANDurl
    LIST_NAME = names
    MODE = Geometry - Assemble One Level
    SEP = ,
    AGGREGATE -> ListConcatenator_13
ListConcatenator_13
    DROP_EMPTY_PARTS = No
    LIST_ATTR = names{}.nameANDurl
    SEP = ;
    VAL_ATTR = PlayerLink
    -> FeatureMerger_6 [REQUESTOR]
Aggregator_12
    ACCUM_ATTRS_NAME = Use Attributes From One Feature
    AGGREGATE_TYPE = Homogeneous Collection (If Possible)
    GROUP_BY = nationality
    LIST_ATTRS_TO_INCLUDE = nameANDurl
    LIST_NAME = names
    MODE = Geometry - Assemble One Level
    SEP = ,
    AGGREGATE -> ListConcatenator_12
ListConcatenator_12
    DROP_EMPTY_PARTS = No
    LIST_ATTR = names{}.nameANDurl
    SEP = ;
    VAL_ATTR = PlayerLink
    -> FeatureMerger_6 [REQUESTOR]
Aggregator_11
    ACCUM_ATTRS_NAME = Use Attributes From One Feature
    AGGREGATE_TYPE = Homogeneous Collection (If Possible)
    GROUP_BY = nationality
    LIST_ATTRS_TO_INCLUDE = nameANDurl
    LIST_NAME = names
    MODE = Geometry - Assemble One Level
    SEP = ,
    AGGREGATE -> ListConcatenator_11
ListConcatenator_11
    DROP_EMPTY_PARTS = No
    LIST_ATTR = names{}.nameANDurl
    SEP = ;
    VAL_ATTR = PlayerLink
    -> FeatureMerger_6 [REQUESTOR]
Aggregator_10
    ACCUM_ATTRS_NAME = Use Attributes From One Feature
    AGGREGATE_TYPE = Homogeneous Collection (If Possible)
    GROUP_BY = nationality
    LIST_ATTRS_TO_INCLUDE = nameANDurl
    LIST_NAME = names
    MODE = Geometry - Assemble One Level
    SEP = ,
    AGGREGATE -> ListConcatenator_10
ListConcatenator_10
    DROP_EMPTY_PARTS = No
    LIST_ATTR = names{}.nameANDurl
    SEP = ;
    VAL_ATTR = PlayerLink
    -> FeatureMerger_6 [REQUESTOR]
Aggregator_9
    ACCUM_ATTRS_NAME = Use Attributes From One Feature
    AGGREGATE_TYPE = Homogeneous Collection (If Possible)
    GROUP_BY = nationality
    LIST_ATTRS_TO_INCLUDE = nameANDurl
    LIST_NAME = names
    MODE = Geometry - Assemble One Level
    SEP = ,
    AGGREGATE -> ListConcatenator_9
ListConcatenator_9
    DROP_EMPTY_PARTS = No
    LIST_ATTR = names{}.nameANDurl
    SEP = ;
    VAL_ATTR = PlayerLink
    -> FeatureMerger_6 [REQUESTOR]
Aggregator_8
    ACCUM_ATTRS_NAME = Use Attributes From One Feature
    AGGREGATE_TYPE = Homogeneous Collection (If Possible)
    GROUP_BY = nationality
    LIST_ATTRS_TO_INCLUDE = nameANDurl
    LIST_NAME = names
    MODE = Geometry - Assemble One Level
    SEP = ,
    AGGREGATE -> ListConcatenator_8
ListConcatenator_8
    DROP_EMPTY_PARTS = No
    LIST_ATTR = names{}.nameANDurl
    SEP = ;
    VAL_ATTR = PlayerLink
    -> FeatureMerger_6 [REQUESTOR]
Aggregator_7
    ACCUM_ATTRS_NAME = Use Attributes From One Feature
    AGGREGATE_TYPE = Homogeneous Collection (If Possible)
    GROUP_BY = nationality
    LIST_ATTRS_TO_INCLUDE = nameANDurl
    LIST_NAME = names
    MODE = Geometry - Assemble One Level
    SEP = ,
    AGGREGATE -> ListConcatenator_7
ListConcatenator_7
    DROP_EMPTY_PARTS = No
    LIST_ATTR = names{}.nameANDurl
    SEP = ;
    VAL_ATTR = PlayerLink
    -> FeatureMerger_6 [REQUESTOR]
Aggregator_6
    ACCUM_ATTRS_NAME = Use Attributes From One Feature
    AGGREGATE_TYPE = Homogeneous Collection (If Possible)
    GROUP_BY = nationality
    LIST_ATTRS_TO_INCLUDE = nameANDurl
    LIST_NAME = names
    MODE = Geometry - Assemble One Level
    SEP = ,
    AGGREGATE -> ListConcatenator_6
ListConcatenator_6
    DROP_EMPTY_PARTS = No
    LIST_ATTR = names{}.nameANDurl
    SEP = ;
    VAL_ATTR = PlayerLink
    -> FeatureMerger_6 [REQUESTOR]
Aggregator_5
    ACCUM_ATTRS_NAME = Use Attributes From One Feature
    AGGREGATE_TYPE = Homogeneous Collection (If Possible)
    GROUP_BY = nationality
    LIST_ATTRS_TO_INCLUDE = nameANDurl
    LIST_NAME = names
    MODE = Geometry - Assemble One Level
    SEP = ,
    AGGREGATE -> ListConcatenator_5
ListConcatenator_5
    DROP_EMPTY_PARTS = No
    LIST_ATTR = names{}.nameANDurl
    SEP = ;
    VAL_ATTR = PlayerLink
    -> FeatureMerger_6 [REQUESTOR]
Aggregator_4
    ACCUM_ATTRS_NAME = Use Attributes From One Feature
    AGGREGATE_TYPE = Homogeneous Collection (If Possible)
    GROUP_BY = nationality
    LIST_ATTRS_TO_INCLUDE = nameANDurl
    LIST_NAME = names
    MODE = Geometry - Assemble One Level
    SEP = ,
    AGGREGATE -> ListConcatenator_4
ListConcatenator_4
    DROP_EMPTY_PARTS = No
    LIST_ATTR = names{}.nameANDurl
    SEP = ;
    VAL_ATTR = PlayerLink
    -> FeatureMerger_6 [REQUESTOR]
Aggregator_3
    ACCUM_ATTRS_NAME = Use Attributes From One Feature
    AGGREGATE_TYPE = Homogeneous Collection (If Possible)
    GROUP_BY = nationality
    LIST_ATTRS_TO_INCLUDE = nameANDurl
    LIST_NAME = names
    MODE = Geometry - Assemble One Level
    SEP = ,
    AGGREGATE -> ListConcatenator_3
ListConcatenator_3
    DROP_EMPTY_PARTS = No
    LIST_ATTR = names{}.nameANDurl
    SEP = ;
    VAL_ATTR = PlayerLink
    -> FeatureMerger_6 [REQUESTOR]
Aggregator_2
    ACCUM_ATTRS_NAME = Use Attributes From One Feature
    AGGREGATE_TYPE = Homogeneous Collection (If Possible)
    GROUP_BY = nationality
    LIST_ATTRS_TO_INCLUDE = nameANDurl
    LIST_NAME = names
    MODE = Geometry - Assemble One Level
    SEP = ,
    AGGREGATE -> ListConcatenator_2
ListConcatenator_2
    DROP_EMPTY_PARTS = No
    LIST_ATTR = names{}.nameANDurl
    SEP = ;
    VAL_ATTR = PlayerLink
    -> FeatureMerger_6 [REQUESTOR]
Aggregator
    ACCUM_ATTRS_NAME = Use Attributes From One Feature
    AGGREGATE_TYPE = Homogeneous Collection (If Possible)
    GROUP_BY = nationality
    LIST_ATTRS_TO_INCLUDE = nameANDurl
    LIST_NAME = names
    MODE = Geometry - Assemble One Level
    SEP = ,
    AGGREGATE -> ListConcatenator
ListConcatenator
    DROP_EMPTY_PARTS = No
    LIST_ATTR = names{}.nameANDurl
    SEP = ;
    VAL_ATTR = PlayerLink
    -> FeatureMerger_6 [REQUESTOR]
FeatureMerger_6
    ATTR_ACCUM_MODE = Merge Supplier
    ATTR_CONFLICT_RES = Use Requestor
    GROUP_BY = Team
    IGNORE_NULLS = No
    JOIN_KEYS = @Value(nationality) @Value(value) AUTO
    MERGE_TYPE = Attributes Only
    PROCESS_DUPS = NO
    REJECT_NULL_MISSING_KEYS = No
    SUPPLIERS_FIRST = No
    MERGED -> AttributeManager_2
AttributeManager_2
    ATTR_TABLE:
      REMOVE key
      REMOVE player_url
      REMOVE short_name
      REMOVE long_name
      REMOVE age
      REMOVE club
      REMOVE nameANDurl
      REMOVE names{}.nameANDurl
      RENAME_SET_VALUE PlayerLink > PlayersNames
      REMOVE uniqueLogger{}._count
      REMOVE uniqueLogger{}._value
      RENAME_SET_VALUE count > PlayersNr
      REMOVE value
      REMOVE _element_index
    -> AttributeFilter_2
AttributeFilter_2
    ATTR_NAME = Team
    ATTR_VALUES = <Empty>,<Missing>,<Null>,<Unfiltered>,Arsenal ,Aston Villa ,Brighton & Hove Albion ,Burnley ,Chelsea ,Crystal Palace ,Everton ,Leicester City ,Liverpool ,Manchester City ,Manchester United ,Newcastle United ,Norwich City ,Sheffield United,Southampton ,Tottenham Hotspur ,Watford ,West Ham United ,Wolverhampton Wanderers ,Bournemouth
    Arsenal -> DuplicateFilter_20
    Aston Villa -> DuplicateFilter_19
    Brighton & Hove Albion -> DuplicateFilter_18
    Burnley -> DuplicateFilter_17
    Chelsea -> DuplicateFilter_16
    Crystal Palace -> DuplicateFilter_15
    Everton -> DuplicateFilter_14
    Leicester City -> DuplicateFilter_13
    Liverpool -> DuplicateFilter_12
    Manchester City -> DuplicateFilter_11
    Manchester United -> DuplicateFilter_10
    Newcastle United -> DuplicateFilter_9
    Norwich City -> DuplicateFilter_8
    Sheffield United -> DuplicateFilter_7
    Southampton -> DuplicateFilter_6
    Tottenham Hotspur -> DuplicateFilter_5
    Watford -> DuplicateFilter_4
    West Ham United -> DuplicateFilter_3
    Wolverhampton Wanderers -> DuplicateFilter_2
    Bournemouth -> DuplicateFilter
DuplicateFilter_20
    INPUT_ORDERED_CHOICE = No
    KEYATTR = nationality
    UNIQUE -> NewFeatureType (writer JSON_2)
    UNIQUE -> StringConcatenator_2
NewFeatureType (writer JSON_2)
    attributes: nationality string, Team string, LongCentroid float, LatCentroid float, PlayersNames string, PlayersNr int
DuplicateFilter_19
    INPUT_ORDERED_CHOICE = No
    KEYATTR = nationality
    UNIQUE -> NewFeatureType (writer JSON_3)
    UNIQUE -> StringConcatenator_2
NewFeatureType (writer JSON_3)
    attributes: nationality string, Team string, LongCentroid float, LatCentroid float, PlayersNames string, PlayersNr int
DuplicateFilter_18
    INPUT_ORDERED_CHOICE = No
    KEYATTR = nationality
    UNIQUE -> NewFeatureType (writer JSON_4)
    UNIQUE -> StringConcatenator_2
NewFeatureType (writer JSON_4)
    attributes: nationality string, Team string, LongCentroid float, LatCentroid float, PlayersNames string, PlayersNr int
DuplicateFilter_17
    INPUT_ORDERED_CHOICE = No
    KEYATTR = nationality
    UNIQUE -> NewFeatureType (writer JSON_5)
    UNIQUE -> StringConcatenator_2
NewFeatureType (writer JSON_5)
    attributes: nationality string, Team string, LongCentroid float, LatCentroid float, PlayersNames string, PlayersNr int
DuplicateFilter_16
    INPUT_ORDERED_CHOICE = No
    KEYATTR = nationality
    UNIQUE -> NewFeatureType (writer JSON_6)
    UNIQUE -> StringConcatenator_2
NewFeatureType (writer JSON_6)
    attributes: nationality string, Team string, LongCentroid float, LatCentroid float, PlayersNames string, PlayersNr int
DuplicateFilter_15
    INPUT_ORDERED_CHOICE = No
    KEYATTR = nationality
    UNIQUE -> NewFeatureType (writer JSON_7)
    UNIQUE -> StringConcatenator_2
NewFeatureType (writer JSON_7)
    attributes: nationality string, Team string, LongCentroid float, LatCentroid float, PlayersNames string, PlayersNr int
DuplicateFilter_14
    INPUT_ORDERED_CHOICE = No
    KEYATTR = nationality
    UNIQUE -> NewFeatureType (writer JSON_8)
    UNIQUE -> StringConcatenator_2
NewFeatureType (writer JSON_8)
    attributes: nationality string, Team string, LongCentroid float, LatCentroid float, PlayersNames string, PlayersNr int
DuplicateFilter_13
    INPUT_ORDERED_CHOICE = No
    KEYATTR = nationality
    UNIQUE -> NewFeatureType (writer JSON_9)
    UNIQUE -> StringConcatenator_2
NewFeatureType (writer JSON_9)
    attributes: nationality string, Team string, LongCentroid float, LatCentroid float, PlayersNames string, PlayersNr int
DuplicateFilter_12
    INPUT_ORDERED_CHOICE = No
    KEYATTR = nationality
    UNIQUE -> NewFeatureType (writer JSON_10)
    UNIQUE -> StringConcatenator_2
NewFeatureType (writer JSON_10)
    attributes: nationality string, Team string, LongCentroid float, LatCentroid float, PlayersNames string, PlayersNr int
DuplicateFilter_11
    INPUT_ORDERED_CHOICE = No
    KEYATTR = nationality
    UNIQUE -> NewFeatureType (writer JSON_11)
    UNIQUE -> StringConcatenator_2
NewFeatureType (writer JSON_11)
    attributes: nationality string, Team string, LongCentroid float, LatCentroid float, PlayersNames string, PlayersNr int
DuplicateFilter_10
    INPUT_ORDERED_CHOICE = No
    KEYATTR = nationality
    UNIQUE -> NewFeatureType (writer JSON_12)
    UNIQUE -> StringConcatenator_2
NewFeatureType (writer JSON_12)
    attributes: nationality string, Team string, LongCentroid float, LatCentroid float, PlayersNames string, PlayersNr int
DuplicateFilter_9
    INPUT_ORDERED_CHOICE = No
    KEYATTR = nationality
    UNIQUE -> NewFeatureType (writer JSON_13)
    UNIQUE -> StringConcatenator_2
NewFeatureType (writer JSON_13)
    attributes: nationality string, Team string, LongCentroid float, LatCentroid float, PlayersNames string, PlayersNr int
DuplicateFilter_8
    INPUT_ORDERED_CHOICE = No
    KEYATTR = nationality
    UNIQUE -> NewFeatureType (writer JSON_14)
    UNIQUE -> StringConcatenator_2
NewFeatureType (writer JSON_14)
    attributes: nationality string, Team string, LongCentroid float, LatCentroid float, PlayersNames string, PlayersNr int
DuplicateFilter_7
    INPUT_ORDERED_CHOICE = No
    KEYATTR = nationality
    UNIQUE -> NewFeatureType (writer JSON_15)
    UNIQUE -> StringConcatenator_2
NewFeatureType (writer JSON_15)
    attributes: nationality string, Team string, LongCentroid float, LatCentroid float, PlayersNames string, PlayersNr int
DuplicateFilter_6
    INPUT_ORDERED_CHOICE = No
    KEYATTR = nationality
    UNIQUE -> NewFeatureType (writer JSON_16)
    UNIQUE -> StringConcatenator_2
NewFeatureType (writer JSON_16)
    attributes: nationality string, Team string, LongCentroid float, LatCentroid float, PlayersNames string, PlayersNr int
DuplicateFilter_5
    INPUT_ORDERED_CHOICE = No
    KEYATTR = nationality
    UNIQUE -> NewFeatureType (writer JSON_17)
    UNIQUE -> StringConcatenator_2
NewFeatureType (writer JSON_17)
    attributes: nationality string, Team string, LongCentroid float, LatCentroid float, PlayersNames string, PlayersNr int
DuplicateFilter_4
    INPUT_ORDERED_CHOICE = No
    KEYATTR = nationality
    UNIQUE -> NewFeatureType (writer JSON_18)
    UNIQUE -> StringConcatenator_2
NewFeatureType (writer JSON_18)
    attributes: nationality string, Team string, LongCentroid float, LatCentroid float, PlayersNames string, PlayersNr int
DuplicateFilter_3
    INPUT_ORDERED_CHOICE = No
    KEYATTR = nationality
    UNIQUE -> NewFeatureType (writer JSON_19)
    UNIQUE -> StringConcatenator_2
NewFeatureType (writer JSON_19)
    attributes: nationality string, Team string, LongCentroid float, LatCentroid float, PlayersNames string, PlayersNr int
DuplicateFilter_2
    INPUT_ORDERED_CHOICE = No
    KEYATTR = nationality
    UNIQUE -> NewFeatureType (writer JSON_20)
    UNIQUE -> StringConcatenator_2
NewFeatureType (writer JSON_20)
    attributes: nationality string, Team string, LongCentroid float, LatCentroid float, PlayersNames string, PlayersNr int
DuplicateFilter
    INPUT_ORDERED_CHOICE = No
    KEYATTR = nationality
    UNIQUE -> NewFeatureType (writer JSON_1)
    UNIQUE -> StringConcatenator_2
Aggregator_24
    ACCUM_ATTRS_NAME = Use Attributes From One Feature
    AGGREGATE_TYPE = Homogeneous Collection (If Possible)
    GROUP_BY = nationality
    MODE = Geometry - Assemble One Level
    SEP = ,
    SUM = PlayersNr
    AGGREGATE -> AttributeRemover_8
AttributeRemover_8
    REMOVE_ATTRS = _sup_supcol68,PlayersNames,Team,nationPlayersnr
    -> AttributeRenamer
AttributeRenamer
    ATTR_TABLE = RENAME_SET_DEFAULT PlayersNr > PlayersNames
    -> Countries (writer JSON_21)
Countries (writer JSON_21)
    attributes: PlayersNames string, nationality string, LongCentroid float, LatCentroid float
NewFeatureType (writer JSON_1)
    attributes: nationality string, Team string, LongCentroid float, LatCentroid float, PlayersNames string, PlayersNr int
CSV: Inspector
AttributeRemover_7
    REMOVE_ATTRS = HomeTeam,key,Capacity,City,Country,FDCOUK,Latitude,listOfNations,listOfNationsPlayers,Longitude,Stadium
    -> AttributeRemover_7_Output
AttributeRemover_7_Output: Inspector
NewFeatureType (writer GEOJSON_3) [off]
    attributes: Team string, FDCOUK string, City string, Stadium string, Capacity int, Latitude float, Longitude float, Country string, nrOfNations int, listOfNations string, listOfNationsPlayers string

Bookmark: teams only in PL 2019/20
TeamLocations (reader GEOJSON_1)
    attributes: HomeTeam int, key string, Team string, FDCOUK string, City string, Stadium string, Capacity int, Latitude float, Longitude float, Country string
    -> FeatureMerger [REQUESTOR]

Bookmark: players
CSV (reader CSV2_1)
    attributes: sofifa_id uint32, player_url string, short_name string, long_name string, age uint8, dob string, height_cm uint8, weight_kg uint8, nationality string, club string, overall uint8, potential uint8, value_eur uint32, wage_eur uint32, player_positions string, preferred_foot string, international_reputation uint8, weak_foot uint8, skill_moves uint8, work_rate string, body_type string, real_face string, release_clause_eur uint32, player_tags string, team_position string, team_jersey_number uint8, loaned_from string, joined string, contract_valid_until uint16, nation_position string,
      nation_jersey_number uint8, pace uint8, shooting uint8, passing uint8, dribbling uint8, defending uint8, physic uint8, gk_diving uint8, gk_handling uint8, gk_kicking uint8, gk_reflexes uint8, gk_speed uint8, gk_positioning uint8, player_traits string, attacking_crossing uint8, attacking_finishing uint8, attacking_heading_accuracy uint8, attacking_short_passing uint8, attacking_volleys uint8, skill_dribbling uint8, skill_curve uint8, skill_fk_accuracy uint8, skill_long_passing uint8, skill_ball_control uint8, movement_acceleration uint8, movement_sprint_speed uint8, movement_agility uint8, movement_reactions uint8, movement_balance uint8, power_shot_power uint8,
      power_jumping uint8, power_stamina uint8, power_strength uint8, power_long_shots uint8, mentality_aggression uint8, mentality_interceptions uint8, mentality_positioning uint8, mentality_vision uint8, mentality_penalties uint8, mentality_composure uint8, defending_marking uint8, defending_standing_tackle uint8, defending_sliding_tackle uint8, goalkeeping_diving uint8, goalkeeping_handling uint8, goalkeeping_kicking uint8, goalkeeping_positioning uint8, goalkeeping_reflexes uint8, ls string, st string, rs string, lw string, lf string, cf string, rf string, rw string, lam string, cam string, ram string, lm string,
      lcm string, cm string, rcm string, rm string, lwb string, ldm string, cdm string, rdm string, rwb string, lb string, lcb string, cb string, rcb string, rb string
    -> FeatureMerger_2 [REQUESTOR]

Bookmark: world centroids
CSV (reader CSV2_2) [off]
    attributes: FID string, the_geom string, FID_ uint8, scalerank uint8, featurecla string, labelrank uint8, sovereignt string, sov_a3 string, adm0_dif uint8, level uint8, type string, admin string, adm0_a3 string, geou_dif uint8, geounit string, gu_a3 string, su_dif uint8, subunit string, su_a3 string, brk_diff uint8, name string, name_long string, brk_a3 string, brk_name string, brk_group string, abbrev string, postal string, formal_en string, formal_fr string, note_adm0 string,
      note_brk string, name_sort string, name_alt string, mapcolor7 uint8, mapcolor8 uint8, mapcolor9 uint8, mapcolor13 int8, pop_est int32, gdp_md_est real64, pop_year int16, lastcensus int16, gdp_year int16, economy string, income_grp string, wikipedia int8, fips_10 string, iso_a2 string, iso_a3 string, iso_n3 int16, un_a3 int16, wb_a2 string, wb_a3 string, woe_id int8, adm0_a3_is string, adm0_a3_us string, adm0_a3_un int8, adm0_a3_wb int8, continent string, region_un string, subregion string,
      region_wb string, name_len uint8, long_len x_coordinate, abbrev_len uint8, tiny int8, homepart int8, Longitude real64, Latitude y_coordinate
    -> FeatureMerger_2 [SUPPLIER]
    -> CSV

Bookmark: create overall statistics and add them to stadiums points
UniqueValueLogger
    VAL = @Value(nationality)
    -> PointOnPointOverlayer [POINT]
PointOnPointOverlayer
    DEAGGREGATE_INPUT = Yes
    LIST_ATTRS_TO_INCLUDE = _count _value
    LIST_NAME = uniqueLogger
    OV_ATTR = _overlaps
    TOLERANCE = 0
    POINT -> Counter
Counter
    CNT_ATTR = _count
    DOMAIN = @Value(Team)
    SCOPE = Local
    START = 1
    -> TestFilter
TestFilter
    DEFAULT_VALUE = <UNFILTERED>
    TEST_LIST:
      "BOOL_OP,AND,COMPOSITE_TEST,""""""1 AND 2"""""",TEST_CLAUSE,TEST @Value(_count) = 1
      TEST Team ATTRIBUTE_HAS_A_VALUE """,1
    1 -> AttributeRemover_3
AttributeRemover_3
    REMOVE_ATTRS = LatCentroid,LongCentroid,_count,_overlaps,_value,age,club,long_name,nationality,player_url,short_name,nameANDurl
    -> ListHistogrammer
ListHistogrammer
    LIST_NAME = _histogram
    SRC_LIST = uniqueLogger{}._value
    -> ListExploder_2
ListExploder_2
    ATTR_ACCUM_MODE = Merge List Attributes
    ATTR_CONFLICT_RES = Use List Attribute Values
    INDEX_ATTR = _element_index
    LIST_ATTR = _histogram{}
    ELEMENTS -> FeatureMerger_6 [SUPPLIER]
    ELEMENTS -> Aggregator_22

Bookmark: new points for stadiums 2D
StringConcatenator_2
    ACTION = Create New Attribute
    PARM_LINE = fme_basicstring:19%2%17:@Value(nationality): @Value(PlayersNr)
    VAL_ATTR = nationPlayersnr
    -> Counter_2
    -> Aggregator_24
Counter_2
    CNT_ATTR = nrOfNations
    DOMAIN = @Value(Team)
    SCOPE = Local
    START = 1
    -> Sorter
Sorter
    SORT_PARM = nrOfNations NUMERIC DESCENDING
    SORTED -> Aggregator_23
Aggregator_23
    ACCUM_ATTRS_NAME = Use Attributes From One Feature
    AGGREGATE_TYPE = Homogeneous Collection (If Possible)
    GROUP_BY = Team
    LIST_ATTRS_TO_INCLUDE = nationality nationPlayersnr
    LIST_NAME = nationalityList
    MODE = Geometry - Assemble One Level
    SEP = ,
    AGGREGATE -> ListConcatenator_22
    AGGREGATE -> Aggregator_23_Aggregate
ListConcatenator_22
    DROP_EMPTY_PARTS = No
    LIST_ATTR = nationalityList{}.nationality
    SEP = ", "
    VAL_ATTR = listOfNations
    -> ListConcatenator_23
ListConcatenator_23
    DROP_EMPTY_PARTS = No
    LIST_ATTR = nationalityList{}.nationPlayersnr
    SEP = ", "
    VAL_ATTR = listOfNationsPlayers
    -> AttributeRemover_5
Aggregator_23_Aggregate: Inspector

Bookmark: add geometry
AttributeRemover_5
    LIST_ATTRS = nationalityList{} nationalityList{}.nationPlayersnr nationalityList{}.nationality
    REMOVE_ATTRS = LatCentroid,LongCentroid,PlayersNames,PlayersNr,nationPlayersnr,nationality
    -> FeatureMerger_3 [SUPPLIER]
TeamLocations (reader GEOJSON_2)
    attributes: HomeTeam int, key string, Team string, FDCOUK string, City string, Stadium string, Capacity int, Latitude float, Longitude float, Country string
    -> FeatureMerger_3 [REQUESTOR]
FeatureMerger_3
    ATTR_ACCUM_MODE = Merge Supplier
    ATTR_CONFLICT_RES = Use Requestor
    IGNORE_NULLS = No
    JOIN_KEYS = @Value(Team) @Value(Team) AUTO
    MERGE_TYPE = Attributes Only
    PROCESS_DUPS = NO
    REJECT_NULL_MISSING_KEYS = No
    SUPPLIERS_FIRST = No
    MERGED -> AttributeRemover_6
AttributeRemover_6
    REMOVE_ATTRS = HomeTeam,key
    -> NewFeatureType (writer GEOJSON_3)
    -> AttributeRemover_7

FME custom transformer UniqueValueLogger
Description
This transformer lists all of the unique values for a chosen attribute alongside  a count attribute of the number of occurrences of each of these values. The information is logged in both the Translation Window / Workspace log file, and stored in attributes.
This transformer is useful when you are creating a workspace and need to know the possible values to use in a filter.
Input Ports
Input: This transformer accepts any features with an attribute.
Output Ports
Output: Features are output with the attribute selected as the unique value to filter, and a new attribute containing the number of occurrences of each unique value. All other attributes are removed. 
_count: Number of occurrences of each unique value.
_value: Unique values of selected attribute.
Parameters
Attribute to Analyze: Select the attribute for the transformer to run analysis on. 
Notes
Transformer alternatives:
Duplicate Filter - Consider using this transformer if you are looking to get a list of unique values and do not need a _count attribute 
StatisticsCalculator - Setting the Group By mode to the attribute to analyze will produce the same result as this transformer, it may beuse If you would like to gather other statistics as well as count of the unique attributes.

Parameters:
- VAL =   # Attribute to Analyze

Input (input)
    -> AttributeCreator

Bookmark: Count unique attribute values
AttributeCreator
    ATTR_TABLE = SET_TO _value = $(VAL)
    -> AttributeKeeper
Note: Remove unwanted / attributes
AttributeKeeper
    KEEP_ATTRS = _value
    -> Aggregator
Note: Create aggregates of / features, grouped by / the target attribute value
Aggregator
    ACCUM_ATTRS_NAME = Merge Incoming Attributes
    AGGREGATE_TYPE = Homogeneous Collection (If Possible)
    COUNT_ATTR = _count
    GROUP_BY = _value
    MODE = Geometry - Assemble One Level
    SEP = ,
    AGGREGATE -> StringConcatenator
Note: Concatenate unique values / with their occurrence counts
StringConcatenator
    ACTION = Create New Attribute
    PARM_LINE = fme_basicstring:14%1%14%1:@Value(_value),@Value(_count)
    VAL_ATTR = _concatenated
    -> Sorter
Note: Sort output based on / occurrence count and / attribute value
Sorter
    SORT_PARM = _count NUMERIC DESCENDING _value ALPHA ASCENDING
    SORTED -> ListBuilder
    SORTED -> AttributeManager

Bookmark: Create output
AttributeManager
    ATTR_TABLE = REMOVE _concatenated
    -> Output (output)
Output (output)

Bookmark: Log unique attribute values
Note: Turn all input features / Into a single list
ListBuilder
    LIST_NAME = _list
    -> ListConcatenator
Note: Concatenate values of / the list into an attribute
ListConcatenator
    DROP_EMPTY_PARTS = No
    LIST_ATTR = _list{}._concatenated
    VAL_ATTR = UNIQUE VALUES
    -> StringConcatenator_2
Note: Add header
StringConcatenator_2
    ACTION = Create New Attribute
    PARM_LINE = "\n\nVALUE, COUNT\n@Value(UNIQUE VALUES)\n"
    VAL_ATTR = UNIQUE VALUES
    -> AttributeRemover_2
Note: Remote the list
AttributeRemover_2
    LIST_ATTRS = _list{}
    -> Logger
Note: Log the single feature / that contains the / output attribute
Logger
    LOG_FEATURE = LOG_RECORD
    MAXCOORDS = 1
    MAXFEATS = 1
    MESSAGE = Unique values:
    SEVERITY = INFO
